Option Explicit
'------------------------------------------------------------------------------
'Subroutine: ArrayPointsOnSurface
' Purpose:    Creates an array of points on a surface.
'------------------------------------------------------------------------------

'Call ArrayPtsOnTrimSrf()

Sub ArrayPointsOnSurface()

	Dim strObject, nRows, nColumns
	Dim U, V, i, j, arrParam(1), arrPoint

	' Get the surface object
	strObject = Rhino.GetObject("Select surface", 8)

	If IsNull(strObject) Then Exit Sub
	
	' Get the number of rows
	nRows = Rhino.GetInteger("Number of rows", 2, 2)

	If IsNull(nRows) Then Exit Sub
	
	nRows = nRows - 1
	' Get the number of columns
	nColumns = Rhino.GetInteger("Number of columns", 2, 2)

	If IsNull(nColumns) Then Exit Sub

	nColumns = nColumns - 1

	' Get the domain of the surface
	U = Rhino.SurfaceDomain(strObject, 0)
	V = Rhino.SurfaceDomain(strObject, 1)

	If Not IsArray(U) Or Not IsArray(V) Then Exit Sub

	' Add the points
	For i = 0 To nRows
		arrParam(0) = U(0) + (((U(1) - U(0)) / nRows) * i)
		For j = 0 To nColumns
			arrParam(1) = V(0) + (((V(1) - V(0)) / nColumns) * j)
			arrPoint = Rhino.EvaluateSurface(strObject, arrParam)
			If IsArray(arrPoint) Then Rhino.AddPoint arrPoint
		Next
	Next
End Sub

Sub WhoFramedTheSurface()
	Dim idSurface : idSurface = Rhino.GetObject("Surface to frame", 8, True, True)
	If IsNull(idSurface) Then Exit Sub
	Dim intCount : intCount = Rhino.GetInteger("Number of iterations per direction", 20, 2)
	If IsNull(intCount) Then Exit Sub
	Dim uDomain : uDomain = Rhino.SurfaceDomain(idSurface, 0)
	Dim vDomain : vDomain = Rhino.SurfaceDomain(idSurface, 1)
	Dim uStep : uStep = (uDomain(1) - uDomain(0)) / intCount
	Dim vStep : vStep = (vDomain(1) - vDomain(0)) / intCount
	Dim u, v
	Dim pt
	Dim srfFrame
	Call Rhino.EnableRedraw(False)
	For u = uDomain(0) To uDomain(1) Step uStep
		For v = vdomain(0) To vDomain(1) Step vStep
			pt = Rhino.EvaluateSurface(idSurface, Array(u, v))
			If Rhino.Distance(pt, Rhino.BrepClosestPoint(idSurface, pt)(0)) < 0.1 Then
				srfFrame = Rhino.SurfaceFrame(idSurface, Array(u, v))
				Call Rhino.AddPlaneSurface(srfFrame, 1.0, 1.0)
			End If
		Next
	Next
	Call Rhino.EnableRedraw(True)
End Sub

Call test()
Sub test()
	Dim idSurface : idSurface = Rhino.GetObject("Surface to frame", 8, True, True)
	If IsNull(idSurface) Then Exit Sub
	Dim intSpc : intSpc = Rhino.GetInteger("Enter Grid Spacing", 5, 1)
	If IsNull(intSpc) Then Exit Sub

	Dim arrPts : arrPts = ArrayPtsOnTrimmedSrf(idSurface, intSpc)
	Dim dblStep : dblStep = 2.6
	Call SnapPtsToLevels(arrPts, dblStep)
	
End Sub

Function ArrayPtsOnTrimmedSrf(idSurface, intSpc)
	
	Dim arrPts()
	
	'Dim idSurface : idSurface = Rhino.GetObject("Surface to frame", 8, True, True)
	If IsNull(idSurface) Then Exit Function
	'Dim intSpc : intSpc = Rhino.GetInteger("Enter Grid Spacing", 5, 1)
	If IsNull(intSpc) Then Exit Function
	
	Dim uDomain : uDomain = Rhino.SurfaceDomain(idSurface, 0)
	Dim vDomain : vDomain = Rhino.SurfaceDomain(idSurface, 1)
	'Dim uStep : uStep = (uDomain(1) - uDomain(0)) / intSpc
	'Dim vStep : vStep = (vDomain(1) - vDomain(0)) / intSpc
	
	Dim u, v
	Dim j : j=0
	Dim pt
	Dim srfFrame
	Call Rhino.EnableRedraw(False)
	For u = uDomain(0) To uDomain(1) Step intSpc
		For v = vdomain(0) To vDomain(1) Step intSpc
			pt = Rhino.EvaluateSurface(idSurface, Array(u, v))
			'if pt is not on part of srf that is trimmed away, then add pt
			If Rhino.Distance(pt, Rhino.BrepClosestPoint(idSurface, pt)(0)) < 0.1 Then
				'add pt
				ReDim Preserve arrPts(j)
				'arrPts(j) = pt
				arrPts(j) = Rhino.AddPoint(pt)
				j=j+1
			End If
		Next
	Next
	Call Rhino.EnableRedraw(True)
	
	ArrayPtsOnTrimmedSrf = arrPts
	
End Function

'doesn't work with fractioons
Function SnapPtsToLevels(arrPts, dblStep)
	
	If IsNull(arrPts) Then Exit Function
	If IsNull(dblStep) Then Exit Function
	
	Dim i, pt, idPt, intN
	For i=0 To Ubound(arrPts)
		'get pt ref
		idPt = arrPts(i)
		'get pt coords
		pt =  Rhino.PointCoordinates(idPt)
		'snap down
		intN = Int(pt(2)/dblStep)
		pt(2) = intN * dblStep
		
		'if remainder <= half step size then round down, else up
		'If pt(2) Mod dblStep <= dblStep/2 Then
		'	intN = Int(pt(2)/dblStep)
		'	pt(2) = intN * dblStep
		'ElseIf pt(2) Mod dblStep > dblStep/2 Then
		'	intN = Int(pt(2)/dblStep)
		'	pt(2) = intN * dblStep
		'Else
		'	Rhino.Print "oops, pt(2) Mod dblStep = " + pt(2) Mod dblStep
		'	Exit Function
		'End If
		
		'move pt obj
		Call Rhino.PointCoordinates(idPt, pt)
	Next
End Function
